;;; REP.lsp  柜名标准化替换命令
;;; 命令 REP：选择若干单行/多行文字，将其内容（柜名）替换为标准柜名。
;;; 映射表来源：小命令\文字替换.xlsx （A列=原柜名，B列=标准柜名）
;;; 匹配规则：去除文字首尾空格后，与原柜名整体精确匹配，命中则整体替换为标准柜名。

(defun rep-trim (s)
  (if (null s) (setq s ""))
  (while (and (> (strlen s) 0)
              (member (substr s 1 1) (list " " "\t")))
    (setq s (substr s 2)))
  (while (and (> (strlen s) 0)
              (member (substr s (strlen s) 1) (list " " "\t")))
    (setq s (substr s 1 (1- (strlen s)))))
  s)

(defun c:REP ( / ss i en obj str key pair cnt miss table)
  (vl-load-com)
  (setq table
    (list
      (cons "#2直流馈线柜" "直流馈线柜2")
      (cons "1#直流馈线柜" "直流馈线柜1")
      (cons "#1直流馈线柜" "直流馈线柜1")
      (cons "#2配网综合故障管控PT柜" "10kV#2配网综合故障管控PT柜")
      (cons "#1配网综合故障管控PT柜" "10kV#1配网综合故障管控PT柜")
      (cons "#1主变10kV侧开关柜" "10kV#1主变进线柜")
      (cons "#2主变10kV侧开关柜" "10kV#2主变进线柜")
      (cons "#2配网综合故障管控接地柜" "10kV#2配网综合故障管控接地柜")
      (cons "#1配网综合故障管控接地柜" "10kV#1配网综合故障管控接地柜")
      (cons "#1主变测控柜" "主变测控柜1")
      (cons "#2主变测控柜" "主变测控柜2")
      (cons "#1主变保护柜" "主变保护柜1")
      (cons "#2主变保护柜" "主变保护柜2")
      (cons "#1SVG控制柜" "10kV#1SVG控制柜")
      (cons "#2SVG控制柜" "10kV#2SVG控制柜")
      (cons "10kV#1电容出线柜" "10kV#1电容器出线柜")
      (cons "10kV#2电容出线柜" "10kV#2电容器出线柜")
      (cons "#1电容器" "10kV#1电容器")
      (cons "#2电容器" "10kV#2电容器")
      (cons "调度数据专网柜1" "调度数据网柜1")
      (cons "调度数据专网柜2" "调度数据网柜2")
      (cons "10kV 分段柜" "10kV分段柜")
      (cons "110kV 母线智能汇控柜" "110kV母线智能汇控柜")
      (cons "1#主变保护柜" "主变保护柜1")
      (cons "2#主变保护柜" "主变保护柜2")
      (cons "2#直流馈线柜" "直流馈线柜2")
      (cons "逆功率保护及电能质量在线监测柜" "逆功率保护及电能质量监测柜")
      (cons "逆功率保护及电能质量检测柜" "逆功率保护及电能质量监测柜")
      (cons "时钟同步柜" "时间同步柜")
      (cons "GIS#1主变间隔汇控柜" "#1主变110kV智能控制柜")
      (cons "GIS#2主变间隔汇控柜" "#2主变110kV智能控制柜")
      (cons "GIS线路间隔汇控柜" "110kV线路智能汇控柜")
      (cons "10kV#1电容器开关柜" "10kV#1电容器出线柜")
      (cons "10kV#2电容器开关柜" "10kV#2电容器出线柜")
      (cons "GISPT间隔汇控柜" "110kV母线智能汇控柜")
      (cons "10kV分段隔离柜" "10kV隔离柜")
      (cons "10kV1#SVG开关柜" "10kV#1SVG出线柜")
      (cons "10kV2#SVG开关柜" "10kV#2SVG出线柜")
      (cons "#1主变中性点成套装置" "#1主变中性点隔离开关机构")
      (cons "#2主变中性点成套装置" "#2主变中性点隔离开关机构")
      (cons "#1主变有载开关" "#1主变有载调压端子箱")
      (cons "#2主变有载开关" "#2主变有载调压端子箱")
      (cons "#1主变风冷控制柜1" "#1主变风冷控制柜")
      (cons "#1主变风冷控制柜2" "#1主变风冷控制柜")
      (cons "#2主变风冷控制柜1" "#2主变风冷控制柜")
      (cons "#2主变风冷控制柜2" "#2主变风冷控制柜")
      (cons "#1主变油色谱在线监测主机" "#1主变油色谱就地柜")
      (cons "#2主变油色谱在线监测主机" "#2主变油色谱就地柜")
      (cons "在线监测后台主机" "在线监测后台柜")
      (cons "主变油色谱在线监测后台主机柜" "在线监测后台柜")
      (cons "110kV进线间隔GIS汇控柜" "110kV线路智能汇控柜")
      (cons "110kVPT间隔GIS汇控柜" "110kV母线智能汇控柜")
      (cons "#1电容器组" "10kV#1电容器")
      (cons "#2电容器组" "10kV#2电容器")
      (cons "10kV#1电容器组" "10kV#1电容器")
      (cons "10kV#2电容器组" "10kV#2电容器")
      (cons "10kV#1电容器端子箱" "10kV#1电容器")
      (cons "10kV#2电容器端子箱" "10kV#2电容器")
      (cons "#1-1储能并网柜" "10kV#1-1储能出线柜")
      (cons "#1-2储能并网柜" "10kV#1-2储能出线柜")
      (cons "#1-3储能并网柜" "10kV#1-3储能出线柜")
      (cons "#1-4储能并网柜" "10kV#1-4储能出线柜")
      (cons "#2-1储能并网柜" "10kV#2-1储能出线柜")
      (cons "2-2#储能并网柜" "10kV#2-2储能出线柜")
      (cons "#2-3储能并网柜" "10kV#2-3储能出线柜")
      (cons "#2-4储能并网柜" "10kV#2-4储能出线柜")
    )
  )
  (princ "\n请选择要替换的文字（单行文字/多行文字）：")
  (setq ss (ssget (list (cons 0 "TEXT,MTEXT"))))
  (if ss
    (progn
      (setq cnt 0 miss 0 i 0)
      (while (< i (sslength ss))
        (setq en (ssname ss i))
        (setq obj (vlax-ename->vla-object en))
        (setq str (vlax-get obj (quote TextString)))
        (setq key (rep-trim str))
        (setq pair (assoc key table))
        (if pair
          (progn
            (vlax-put obj (quote TextString) (cdr pair))
            (setq cnt (1+ cnt)))
          (setq miss (1+ miss)))
        (setq i (1+ i)))
      (princ (strcat "\n替换完成：成功 " (itoa cnt) " 个，未匹配 " (itoa miss) " 个。")))
    (princ "\n未选择任何文字。"))
  (princ)
)
(princ "\nREP 柜名标准化替换命令已加载，输入 REP 运行。")
(princ)
